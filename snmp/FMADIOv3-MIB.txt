FMADIOv3-MIB DEFINITIONS ::= BEGIN

--
--  FMADIO SNMP traps
--

IMPORTS
    MODULE-IDENTITY, NOTIFICATION-TYPE, OBJECT-TYPE, Integer32, Counter64, enterprises FROM SNMPv2-SMI
;

fmadio MODULE-IDENTITY
    LAST-UPDATED "202307250000Z"
    ORGANIZATION "fmad.io"
    CONTACT-INFO "email: support@fmad.io"
	DESCRIPTION  "fmadio MIB for trap events"
	REVISION     "202307250000Z"
    DESCRIPTION  
				"initial trap release"
    ::= { enterprises 46891 }

--
-- top level structure
--
fmadioScalars                      OBJECT IDENTIFIER ::= { fmadio 1 }
fmadioNotifications                OBJECT IDENTIFIER ::= { fmadio 2 }
fmadioNotificationObjects          OBJECT IDENTIFIER ::= { fmadio 3 }

fmadioCapture          		   OBJECT IDENTIFIER ::= { fmadio 4 }

fmadioInt32 OBJECT-TYPE
              SYNTAX  Integer32
              MAX-ACCESS  read-only
			  STATUS      current
              DESCRIPTION
                      "A unique value for each interface.  Its value
                      ranges between 1 and the value of ifNumber.  The
                      value for each interface must remain constant at
                      least from one re-initialization of the entity's
                      network management system to the next re-
                      initialization."
              ::= { fmadioScalars 1 }


fmadioInt64 OBJECT-TYPE
              SYNTAX  Counter64
              MAX-ACCESS  read-only
			  STATUS      current
              DESCRIPTION
                      "A unique value for each interface.  Its value
                      ranges between 1 and the value of ifNumber.  The
                      value for each interface must remain constant at
                      least from one re-initialization of the entity's
                      network management system to the next re-
                      initialization."
              ::= { fmadioScalars 2 }

--
--  Capture Link Status 
--

fmadioCapture0Link NOTIFICATION-TYPE  
	OBJECTS { fmadioInt32 }
    STATUS      current
	DESCRIPTION "FMADIO Capture Link 0 Up"
 
::= { fmadioCapture 1 }

fmadioCapture1Link NOTIFICATION-TYPE 
	OBJECTS { fmadioInt32 }
    STATUS      current
    DESCRIPTION "FMADIO Capture Link 1 Up"

::= { fmadioCapture 2 }

fmadioCapture2Link NOTIFICATION-TYPE 
	OBJECTS { fmadioInt32 }
    STATUS      current
    DESCRIPTION "FMADIO Capture Link 1 Up"

::= { fmadioCapture 3 }

fmadioCapture3Link NOTIFICATION-TYPE 
	OBJECTS { fmadioInt32 }
    STATUS      current
    DESCRIPTION "FMADIO Capture Link 1 Up"

::= { fmadioCapture 4 }

fmadioCapture4Link NOTIFICATION-TYPE 
	OBJECTS { fmadioInt32 }
    STATUS      current
    DESCRIPTION "FMADIO Capture Link 1 Up"

::= { fmadioCapture 5 }

fmadioCapture5Link NOTIFICATION-TYPE 
	OBJECTS { fmadioInt32 }
    STATUS      current
    DESCRIPTION "FMADIO Capture Link 1 Up"

::= { fmadioCapture 6 }

fmadioCapture6Link NOTIFICATION-TYPE 
	OBJECTS { fmadioInt32 }
    STATUS      current
    DESCRIPTION "FMADIO Capture Link 1 Up"

::= { fmadioCapture 7 }

fmadioCapture7Link NOTIFICATION-TYPE 
	OBJECTS { fmadioInt32 }
    STATUS      current
    DESCRIPTION "FMADIO Capture Link 1 Up"

::= { fmadioCapture 8 }



--
-- capture port data
--

fmadioCapturePacket NOTIFICATION-TYPE 
	OBJECTS { fmadioInt64 }
    STATUS      current
    DESCRIPTION "FMADIO Total Packets Captured"

::= { fmadioCapture 10 }


fmadioCaptureByte NOTIFICATION-TYPE
	OBJECTS { fmadioInt64 }
    STATUS      current
    DESCRIPTION "FMADIO Total Bytes Captured"

::= { fmadioCapture 11 }


fmadioCaptureCache NOTIFICATION-TYPE 
	OBJECTS { fmadioInt64 }
    STATUS      current
    DESCRIPTION "FMADIO Total Bytes Cached waiting for writeback to magnetic storage"

::= { fmadioCapture 12 }


fmadioCaptureDrop NOTIFICATION-TYPE 
	OBJECTS { fmadioInt64 }
    STATUS      current
    DESCRIPTION "FMADIO Total Number of packet drops"

::= { fmadioCapture 13 }


fmadioCaptureError NOTIFICATION-TYPE 
	OBJECTS { fmadioInt64 }
    STATUS      current
    DESCRIPTION "FMADIO Total Number of packet errors (e.g. FCS)"

::= { fmadioCapture 14 }


fmadioCaptureOverflow NOTIFICATION-TYPE 
	OBJECTS { fmadioInt64 }
    STATUS      current
    DESCRIPTION "FMADIO Total Bytes Cache Overflow/lost"

::= { fmadioCapture 15 }


--
-- disk status
--

fmadioDiskFreeSystem NOTIFICATION-TYPE 
	OBJECTS { fmadioInt64 }
    STATUS      current
    DESCRIPTION "FMADIO Disk Bytes Free on /mnt/system"

::= { fmadioCapture 20 }

fmadioDiskFreeStore0 NOTIFICATION-TYPE 
	OBJECTS { fmadioInt64 }
    STATUS      current
    DESCRIPTION "FMADIO Disk Bytes Free on /mnt/store0"

::= { fmadioCapture 21 }

fmadioDiskFreeStore1 NOTIFICATION-TYPE 
 	OBJECTS { fmadioInt64 }
    STATUS      current
    DESCRIPTION "FMADIO Disk Bytes Free on /mnt/store1"

::= { fmadioCapture 22 }

fmadioDiskFreeRemote0 NOTIFICATION-TYPE 
 	OBJECTS { fmadioInt64 }
    STATUS      current
    DESCRIPTION "FMADIO Disk Bytes Free on /mnt/remote0"

::= { fmadioCapture 23 }

fmadioDiskFreeRemote1 NOTIFICATION-TYPE 
 	OBJECTS { fmadioInt64 }
    STATUS      current
    DESCRIPTION "FMADIO Disk Bytes Free on /mnt/remote1"

::= { fmadioCapture 24 }

fmadioDiskError NOTIFICATION-TYPE 
 	OBJECTS { fmadioInt64 }
    STATUS      current
    DESCRIPTION "FMADIO Disk Total Errors"

::= { fmadioCapture 25 }

fmadioDiskSMART NOTIFICATION-TYPE 
  	OBJECTS { fmadioInt64 }
    STATUS      current
    DESCRIPTION "FMADIO Disk Total SMART Errors"

::= { fmadioCapture 26 }


--
-- current data rate
--

fmadioCaptureBps NOTIFICATION-TYPE 
  	OBJECTS { fmadioInt64 }
    STATUS      current
    DESCRIPTION "Current Capture Bits per Second"

::= { fmadioCapture 16 }


fmadioCapturePps NOTIFICATION-TYPE 
 	OBJECTS { fmadioInt64 }
    STATUS      current
    DESCRIPTION "FMADIO Current Capture Packets per Second"

::= { fmadioCapture 17 }



--
-- current state 
--

fmadioCaptureEnable NOTIFICATION-TYPE 
  	OBJECTS { fmadioInt32 }
    STATUS      current
    DESCRIPTION "FMADIO Capture Currently Enabled"

::= { fmadioCapture 18 }

--
--  CPU temperature
--

fmadioCPUTemperature NOTIFICATION-TYPE  
  	OBJECTS { fmadioInt32 }
    STATUS      current
    DESCRIPTION "FMADIO CPU Temperature"

::= { fmadioCapture 30 }


--
-- FAN Alert  
--

fmadioFANAlert  NOTIFICATION-TYPE 
	OBJECTS { fmadioInt32 }
    STATUS      current
    DESCRIPTION "FMADIO FAN Alert"

::= { fmadioCapture 31 }

--
--  PSU Status
--

fmadioPSU0  NOTIFICATION-TYPE 
	OBJECTS { fmadioInt32 }
    STATUS      current
    DESCRIPTION "FMADIO PSU 0 Status"

::= { fmadioCapture 32 }

fmadioPSU1  NOTIFICATION-TYPE 
	OBJECTS { fmadioInt32 }
    STATUS      current
    DESCRIPTION "FMADIO PSU 1 Status"

::= { fmadioCapture 33 }


END
